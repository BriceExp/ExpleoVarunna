# Specification Title

# Specification: Specification Document
- Description: System Requirements
- Version: 1

## R25 (Title)
3.1. Functional Requirements

### R71 (Title)
3.1.1. Movement

#### R1 (Requirement Type)
The VARUNA SHALL be able to fly.
- Req-ID: Req_VAR_ FUN_ 0001_V01

#### R4 (Requirement Type)
The VARUNA SHALL be able to navigate on water.
- Req-ID: Req_VAR_ FUN_ 0002_V01

#### R5 (Requirement Type)
The VARUNA SHALL be able to fly at 1000 m altitude.
- Req-ID: Req_VAR_ FUN_ 0003_V01

#### R6 (Requirement Type)
The VARUNA SHALL be able to vertically land from a zone of radius 7 m.
- Req-ID: Req_VAR_ FUN_ 0004_V01

#### R7 (Requirement Type)
The VARUNA SHALL be able to vertically take-off in a zone of radius 7 m.
- Req-ID: Req_VAR_ FUN_ 0005_V01

#### R8 (Requirement Type)
The VARUNA SHALL be able to land from Water.
- Req-ID: Req_VAR_ FUN_ 0006_V01

#### R9 (Requirement Type)
The VARUNA SHALL be able to take-off in a water.
- Req-ID: Req_VAR_ FUN_ 0007_V01

### R72 (Title)
3.1.2. Transfer

#### R10 (Requirement Type)
The VARUNA SHALL be able to transport 4 persons including the pilot.
- Req-ID: Req_VAR_ FUN_ 0008_V01

#### R11 (Requirement Type)
The VARUNA SHOULD allow to bord a stretcher.
- Req-ID: Req_VAR_ FUN_ 0009_V01

#### R12 (Requirement Type)
The VARUNA WILL allow to bord a fret.
- Req-ID: Req_VAR_ FUN_ 0010_V01

### R73 (Title)
3.1.3. Control

#### R13 (Requirement Type)
The VARUNA SHALL be controlled by 1 pilot maximum.
- Req-ID: Req_VAR_ FUN_ 0011_V01

### R74 (Title)
3.1.4. Operational Performances (Range, Speed, Duration)

#### R14 (Requirement Type)
The VARUNA SHALL cover at least a distance of 40 Km.
- Req-ID: Req_VAR_ FUN_ 0012_V01

#### R15 (Requirement Type)
The VARUNA SHALL reach a maximum cruise speed of 100Km/h.
- Req-ID: Req_VAR_ FUN_ 0013_V01

#### R16 (Requirement Type)
The VARUNA SHALL reach a maximum vertical climb speed of 5 m/s.
- Req-ID: Req_VAR_ FUN_ 0014_V01

#### R17 (Requirement Type)
The VARUNA SHALL assure a flight duration of 1 hour minimum.
- Req-ID: Req_VAR_ FUN_ 0015_V01

#### R18 (Requirement Type)
The VARUNA SHALL reach a maximum speed of 8 Knot on water.
- Req-ID: Req_VAR_ FUN_ 0016_V01

#### R19 (Requirement Type)
The VARUNA SHALL be capable to cross 500m at least on water.
- Req-ID: Req_VAR_ FUN_ 0017_V01

### R75 (Title)
3.1.5. Operational Performances (Wind, Fog, Waves)

#### R20 (Requirement Type)
The VARUNA SHOULD be able to fly when wind speed reaches 50 km/h.
- Req-ID: Req_VAR_ FUN_ 0018_V01

#### R21 (Requirement Type)
The VARUNA SHOULD be able to land and take-off on water when the waves reach 0,5 m heigh.
- Req-ID: Req_VAR_ FUN_ 0019_V01

#### R22 (Requirement Type)
The VARUNA SHOULD be able to land and take off in deep snow without skis.
- Req-ID: Req_VAR_ FUN_ 0020_V01

#### R23 (Requirement Type)
The VARUNA SHOULD be equipped with an anti-icing system.
- Req-ID: Req_VAR_ FUN_ 0021_V01

#### R24 (Requirement Type)
The VARUNA SHOULD assure at least 5 m visibility in fog conditions.
- Req-ID: Req_VAR_ FUN_ 0022_V01

## R26 (Title)
3.2. Non-functional Requirements

### R76 (Title)
3.2.1. Environment and connectivity

#### R27 (Requirement Type)
The VARUNA SHALL be able to analyze its environment.
- Req-ID: Req_VAR_ OPER_ 0001_V01

#### R28 (Requirement Type)
The VARUNA SHALL be able to interact with its environment.
- Req-ID: Req_VAR_ OPER_ 0002_V01

### R77 (Title)
3.2.2. System Physical Characteristics

#### R29 (Requirement Type)
The VARUNA SHALL measure 6,7 m x 6,2 m x 2,5 m.
- Req-ID: Req_VAR_ OPER_ 0003_V01

#### R30 (Requirement Type)
The VARUNA weight SHALL be under 3175 Kg.
- Req-ID: Req_VAR_ OPER_ 0004_V01
- Verification Status: false

### R78 (Title)
3.2.3. Recharge Time

#### R31 (Requirement Type)
The VARUNA Batteries SHOULD be recharged by one person.
- Req-ID: Req_VAR_ OPER_ 0005_V01

#### R32 (Requirement Type)
The VARUNA Batteries SHOULD be recharged in 2 hours.
- Req-ID: Req_VAR_ OPER_ 0006_V01

### R79 (Title)
3.2.4. Passengers Comfort

#### R33 (Requirement Type)
The VARUNA WILL propose an entertainment for passengers.
- Req-ID: Req_VAR_ OPER_ 0007_V01

#### R34 (Requirement Type)
The VARUNA SHOULD assurer a nice environment (temperature, humidity, luminosity).
- Req-ID: Req_VAR_ OPER_ 0008_V01

#### R35 (Requirement Type)
The VARUNA SHOULD be equipped with 5G connection.
- Req-ID: Req_VAR_ OPER_ 0009_V01

### R80 (Title)
3.2.5. Safety

#### R36 (Requirement Type)
The VARUNA SHALL ensure at least a deceleration of 3g for each passenger in case of breakdown.
- Req-ID: Req_VAR_ OPER_ 0010_V01

#### R37 (Requirement Type)
The VARUNA MUST stand to a system failure.
- Req-ID: Req_VAR_ OPER_ 0011_V01

#### R38 (Requirement Type)
The VARUNA MUST stand to a damage on water.
- Req-ID: Req_VAR_ OPER_ 0012_V01

#### R39 (Requirement Type)
The VARUNA MUST stand to a fire damage.
- Req-ID: Req_VAR_ OPER_ 0013_V01

#### R40 (Requirement Type)
The VARUNA MUST be certified cs -27 ​[3]​
- Req-ID: Req_VAR_ OPER_ 0014_V01

# Specification
- Description: Rotor Requirement
- Version: 1

## R2 (Requirement Type)
The aircraft weight shall lift a weight greater than 3.2 t
- Req-ID: Req_VAR_ ROT_0001_V01
- Rationale: For the aircraft to lift.
- Date: 2024-07-11T05:07:33.000+02:00
- Priority: Mandatory
- Risk: 10

## R41 (Requirement Type)
On a stationary flight, the Rotors_Power shall be less than or equal to 1MW.
- Req-ID: Req_VAR_ ROT_0002_V01
- Rationale: To lift the EVTOL, ensure vertical take-off and landing, and withstand disturbances to maintain flight.
- Date: 2024-07-12T03:14:52.000+02:00
- Priority: Mandatory
- Risk: 5

## R42 (Requirement Type)
The ROTORs shall generate a total thrust greater than 32000 N .
- Req-ID: Req_VAR_ ROT_0003_V01
- Rationale: It's the vertical force required to lift 3.2 t (P=m*g).
- Date: 2024-07-12T15:14:42.000+02:00
- Priority: Mandatory
- Risk: 5

## R43 (Requirement Type)
Each rotor shall generate a thrust of 8000 N tolérencement.
- Req-ID: Req_VAR_ ROT_0004_V01
- Rationale: The 32,000N are equally distributed over 4 rotors, making 8,000N per rotor.
- Date: 2024-07-12T15:19:22.000+02:00
- Priority: Mandatory
- Risk: 5

## R44 (Requirement Type)
At the Blade_Tip, the Mach_Number shall be less than 0.7.
- Req-ID: Req_VAR_ ROT_0005_V01
- Rationale: The speed of this EVTOL is less than the speed of sound.
- Date: 2024-07-12T15:20:06.000+02:00
- Priority: Mandatory
- Risk: 5

## R45 (Requirement Type)
Each blades_rotor shall measure less than 1.15 m in radius tolérencement.
- Req-ID: Req_VAR_ ROT_0006_V01
- Rationale: The EVTOL's performance, operation and service life will depend on the design of the blades.
- Date: 2024-07-12T15:24:51.000+02:00
- Priority: Mandatory
- Risk: 5

## R46 (Requirement Type)
Each router shall consume a power less than 0.25 MW .
- Req-ID: Req_VAR_ ROT_0007_V01
- Rationale: To have an EVTOL that guarantees optimum performance while minimizing risks and operational constraints.
- Date: 2024-07-12T15:28:21.000+02:00
- Priority: Mandatory
- Risk: 5

## R47 (Requirement Type)
The rotation speed of the rotor shall be less 1787 tr/min .
- Req-ID: Req_VAR_ ROT_0008_V01
- Rationale: To optimize aerodynamic efficiency, reduce noise and ensure safety.
- Date: 2024-07-12T15:29:19.000+02:00
- Priority: Mandatory
- Risk: 5

## R48 (Requirement Type)
M= 0.7 shall be reached at the end of the blade without risk of vibration or other danger for the blade voix passive.
- Req-ID: Req_VAR_ ROT_0009_V01
- Rationale: To avoid transonic effects that cause increased drag and aerodynamic instabilities.
- Date: 2024-07-12T15:30:32.000+02:00
- Priority: Mandatory
- Risk: 5

## R49 (Requirement Type)
The Rotor torque shall be greater than 600 Nm.
- Req-ID: Req_VAR_ ROT_0010_V01
- Rationale: For sufficient capacity to lift the EVTOL and efficient flight performance during climb, hold and landing.
- Date: 2024-07-12T15:32:00.000+02:00
- Priority: Mandatory
- Risk: 5

## R50 (Requirement Type)
The thickness of the kerning shall not exceed 98 mm négatif.
- Req-ID: Req_VAR_ ROT_0011_V01
- Rationale: To reduce drag, minimize noise and protect rotor components.
- Date: 2024-07-12T15:32:54.000+02:00
- Priority: Mandatory
- Risk: 5

## R51 (Requirement Type)
Each rotor shall distribute the thrust with optimum between the two blades .
- Req-ID: Req_VAR_ ROT_0012_V01
- Rationale: For blade profiling, angle of attack, load distribution and dynamic balance.
- Date: 2024-07-12T15:33:46.000+02:00
- Priority: Mandatory
- Risk: 5

## R52 (Requirement Type)
The fairing shall be aerodynamic .
- Req-ID: Req_VAR_ ROT_0013_V01
- Rationale: Reduces resistive forces, contributes to EVTOL stability and control.
- Date: 2024-07-12T15:34:31.000+02:00
- Priority: Mandatory
- Risk: 5

## R53 (Requirement Type)
The ROTORs shall not exceed 60 db level .
- Req-ID: Req_VAR_ ROT_0014_V01
- Rationale: To comply with noise standards and for safety reasons.
- Date: 2024-07-12T15:35:13.000+02:00
- Priority: Mandatory
- Risk: 5

## R54 (Requirement Type)
The rotors shall have blade length Strictly inferior to 1.15 m.
- Req-ID: Req_VAR_ ROT_0015_V01
- Rationale: The EVTOL's efficiency, operation and service life will depend on the design of the blades. And the length of the blades must be matched to the EVTOL's power output.
- Date: 2024-07-12T15:36:20.000+02:00
- Priority: Mandatory
- Risk: 5

## R55 (Requirement Type)
The rotors shall have the distance between two rotors equal to 20% of the diameter .
- Req-ID: Req_VAR_ ROT_0016_V01
- Rationale: Minimize interactions between the air flows generated by each rotor, avoid collisions.
- Date: 2024-07-12T15:37:11.000+02:00
- Priority: Mandatory
- Risk: 5

## R56 (Requirement Type)
The ROTORs shall limit the thickness of the fairing to a maximum .
- Req-ID: Req_VAR_ ROT_0017_V01
- Rationale: To reduce aerodynamic drag, cut weight and reduce noise and vibration.
- Date: 2024-07-12T15:38:01.000+02:00
- Priority: Mandatory
- Risk: 5

## R57 (Requirement Type)
The rotor fairing shall be able to attenuate the sound as much as possible .
- Req-ID: Req_VAR_ ROT_0018_V01
- Rationale: To meet noise standards and ensure regulatory compliance.
- Date: 2024-07-12T15:38:45.000+02:00
- Priority: Mandatory
- Risk: 5

## R58 (Requirement Type)
The aerodynamics of the blades shall minimize drag sounds as much as possible .
- Req-ID: Req_VAR_ ROT_0019_V01
- Rationale: The EVTOL must comply with noise standards, and noise reduction also contributes to EVTOL safety.
- Date: 2024-07-12T15:39:38.000+02:00
- Priority: Mandatory
- Risk: 5

# Specification
- Description: Motor Requirement
- Version: 1

## R3 (Requirement Type)
The MOTOR_Length shall be less than 350 mm
- Req-ID: Req_VAR_ MOT_0001_V01
- Rationale: For constraints of space, weight and efficiency.
- Date: 2024-07-11T17:10:05.000+02:00
- Priority: Highly desirable
- Risk: 10

## R59 (Requirement Type)
The MOTOR_Diameter shall be less than 112 mm.
- Req-ID: Req_VAR_ MOT_0002_V01
- Rationale: To design more compact motors that fit in with the overall EVTOL design.
- Date: 2024-07-12T16:12:54.000+02:00
- Priority: Mandatory
- Risk: 10

## R60 (Requirement Type)
The MOTOR shall weigh less than 43,9 kg.
- Req-ID: Req_VAR_ MOT_0003_V01
- Rationale: For weight reasons, but also to optimize performance, energy efficiency and safety.
- Date: 2024-07-12T16:16:00.000+02:00
- Priority: Mandatory
- Risk: 10

## R61 (Requirement Type)
The MOTOR shall provide a nominal power of 250 +/-1 KW .
- Req-ID: Req_VAR_ MOT_0004_V01
- Rationale: To provide the thrust required for take-off, flight maintenance and landing.
- Date: 2024-07-12T16:17:20.000+02:00
- Priority: Mandatory
- Risk: 10

## R62 (Requirement Type)
The MOTOR shall provide powers between 250 KW and 300 KW .
- Req-ID: Req_VAR_ MOT_0005_V01
- Rationale: This power range enables the EVTOL to meet all requirements (vertical takeoff, horizontal flight, safety, etc.).
- Date: 2024-07-12T16:18:06.000+02:00
- Priority: Mandatory
- Risk: 10

## R63 (Requirement Type)
When the moto is providing a power of 250+-1KW, the MOTOR_Speed shall be 2100 tr/min tolérencement.
- Req-ID: Req_VAR_ MOT_0006_V01
- Rationale: 250kW is the rated power. 
  The rated speed required to deliver the power that meets EVTOL requirements.
- Date: 2024-07-12T16:19:00.000+02:00
- Priority: Mandatory
- Risk: 10

## R64 (Requirement Type)
The MOTOR shall have a rotation speed associated with the maximal power at 2500 tr/min .
- Req-ID: Req_VAR_ MOT_0007_V01
- Rationale: Maximum speed, which corresponds to maximum power.
- Date: 2024-07-12T16:19:42.000+02:00
- Priority: Mandatory
- Risk: 10

## R65 (Requirement Type)
The MOTOR_Temperature shall be less then 150°C .
- Req-ID: Req_VAR_ MOT_0008_V01
- Rationale: To guarantee reliability, safety and durability.
- Date: 2024-07-12T16:20:32.000+02:00
- Priority: Mandatory
- Risk: 10

## R66 (Requirement Type)
The Power_Density of the Motor shall be greater than or equal to 10 KW/kg.
- Req-ID: Req_VAR_ MOT_0009_V01
- Rationale: A high power density maximizes the EVTOL's load capacity, enabling it to achieve high flight performance.
- Date: 2024-07-12T16:21:25.000+02:00
- Priority: Mandatory
- Risk: 5

## R67 (Requirement Type)
The MOTOR_Efficiency shall be greater than or equal to 90% .
- Req-ID: Req_VAR_ MOT_0010_V01
- Rationale: So that the EVTOL provides the propulsion power it needs.
- Date: 2024-07-12T16:22:29.000+02:00
- Priority: Mandatory
- Risk: 5

## R68 (Requirement Type)
The MOTOR shall be water cooled .
- Req-ID: Req_VAR_ MOT_0011_V01
- Rationale: The MOTOR must be cooled with water to keep the temperature below 150°C.
- Date: 2024-07-12T16:23:09.000+02:00
- Priority: Mandatory
- Risk: 5

## R69 (Requirement Type)
The MOTOR_Maximum_Speed shall be less than 4000 RPM.
- Req-ID: Req_VAR_ MOT_0012_V01
- Rationale: The EVTOL motor is designed to operate at speeds not exceeding RPM.
- Date: 2024-07-12T16:25:48.000+02:00
- Priority: Mandatory
- Risk: 5

## R70 (Requirement Type)
The MOTOR shall be in accordance with the main aeronautical constraints.
- Req-ID: Req_VAR_ MOT_0013_V01
- Rationale: To guarantee reliability, specific performance, safety standards and regulatory compliance.
- Date: 2024-07-12T16:26:49.000+02:00
- Priority: Mandatory
- Risk: 5

# Specification
- Description: Battery Requirements
- Version: 1

## R81 (Requirement Type)
The battery shall weight less than 1000 kg.
- Req-ID: Req_VAR_ BATT_0001_V01
- Rationale: Project Repartition.

### R94 (Requirement Type)
The Battery_Cells shall weight less than 710 kg.
- Req-ID: Req_VAR_ BATT_0001_1_V01
- Rationale: The cells should occupy about 80% of the total mass allocated for the Batteries.

### R95 (Requirement Type)
The Battery_Management_System shall weight less than 290 kg.
- Req-ID: Req_VAR_ BATT_0001_1_V01
- Rationale: The wiring containers usually occupy 29% of the total mass allocated to the Batteries.

## R82 (Requirement Type)
The Battery shall occupy less than 1m3.
- Req-ID: Req_VAR_ BATT_0002_V01
- Rationale: Project Repartition

### R96 (Requirement Type)
The Battery_Length shall be less than
- Req-ID: Req_VAR_ BATT_0002_1_V01
- Rationale: Check with Theophile.

### R97 (Requirement Type)
The Battery_Width shall be less than
- Req-ID: Req_VAR_ BATT_0002_2_V01
- Rationale: Check with Theophile.

### R98 (Requirement Type)
The Battery_Height shall be less than
- Req-ID: Req_VAR_ BATT_0002_3_V01
- Rationale: Check with Theophile.

## R83 (Requirement Type)
The Battery_Storage_Capacity shall be greater than 1.5 MWh.
- Req-ID: Req_VAR_ BATT_0003_V01
- Rationale: Check with Theophile.

### R93 (Requirement Type)
The Battery_Energy_Density shall be greater than 2.2 kWh/kg.
- Req-ID: Req_VAR_ BATT_0003_1_V01
- Rationale: Minimal density = Minimal srored energy/Maximum Battery cells weight.

## R84 (Requirement Type)
The Battery shall generate more than 1.5 MW for 250s.
- Req-ID: Req_VAR_ BATT_0004_V01
- Rationale: To ensure a minimum of 1h autonomy.

## R85 (Requirement Type)
When fully discharged, the Battery shall charge to more than 99% of its capacity in less than 2h.
- Req-ID: Req_VAR_ BATT_0005_V01
- Rationale: Charging time less than 2h. Could be substituted by completely replacing the battery. The Battery shall be replaced by less than two operators in less than 2h.

## R86 (Requirement Type)
The Battery shall emcompass more than 4 Battery_Packs
- Req-ID: Req_VAR_ BATT_0006_V01
- Rationale: For security reasons. Each Battery pack shall supply one rotor. When one of the packs break down, the others will be there to assist emergency landing.

## R87 (Requirement Type)
The Battery_Life shall be greater than 500 cycles.
- Req-ID: Req_VAR_ BATT_0007_V01
- Rationale: We should recharged the Battery less than 500 times.

### R92 (Requirement Type)
After 500 cycles, the Battery_Storage_Capacity shall be greater than 80% of its Capacity after a full charge and before any discharge.
- Req-ID: Req_VAR_ BATT_0007_1_V01
- Rationale: End of life criterion for the Battery.

## R88 (Requirement Type)
When in a Discharge_State, the Battery shall deliver only Direct_Current_Voltage.
- Req-ID: Req_VAR_ BATT_0008_V01
- Rationale: Output voltage type of the Battery.

## R89 (Requirement Type)
During a Full_Discharge, the Battery voltage shall be greater than 350 V and less than 400 V.
- Req-ID: Req_VAR_ BATT_0009_V01
- Rationale: Allowed output voltage during discharge.

### R90 (Requirement Type)
When the Energy_Stored is greather than 99% of Actual_Capacity, the Battery voltage shall be less than 400 V.
- Req-ID: Req_VAR_ BATT_0009_1_V01
- Rationale: Output voltage when fully charged.

### R91 (Requirement Type)
When the Energy_Stored is less than 1% of Actual_Capacity, the Battery voltage shall be greater than 350 V.
- Req-ID: Req_VAR_ BATT_0009_2_V01
- Rationale: Minimum allowed voltage near full discharge.
